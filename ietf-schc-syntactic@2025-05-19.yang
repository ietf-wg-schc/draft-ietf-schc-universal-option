module ietf-schc-syntactic {
  yang-version 1.1;
  namespace "urn:ietf:params:xml:ns:yang:ietf-schc-syntactic";
  prefix schc-syn;

  import ietf-schc {
      prefix ietf-schc;
  }

  organization
    "IETF IPv6 over Low Power Wide-Area Networks (lpwan) working group";
  contact
    "WG Web:   <https://datatracker.ietf.org/wg/lpwan/about/>
     WG List:  <mailto:p-wan@ietf.org>
     Editor:   Laurent Toutain
       <mailto:laurent.toutain@imt-atlantique.fr>
     Editor:   Ana Minaburo
       <mailto:ana@ackl.io>";
  description
     "
     Copyright (c) 2021 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     *************************************************************************

     This module extends the ietf-schc module to include the compound-ack 
     behavior for Ack On Error as defined in RFC YYYY. 
     It introduces a new leaf for Ack on Error defining the format of the
     SCHC Ack and add the possibility to send several bitmaps in a single 
     answer.";

  revision 2025-03-21 {
    description
      "Initial version for RFC YYYY ";
    reference
      "RFC YYYY: OAM";
  }

  identity fid-coap-delta-type {
       base ietf-schc:fid-coap-base-type;
       description
         "test for new options";
       reference
         "RFC 7252 The Constrained Application Protocol (CoAP)";
     }

  identity fid-coap-length {
       base ietf-schc:fid-coap-base-type;
       description
         "test for new options";
       reference
         "RFC 7252 The Constrained Application Protocol (CoAP)";
     }

   identity fid-coap-value {
       base ietf-schc:fid-coap-base-type;
       description
         "test for new options";
       reference
         "RFC 7252 The Constrained Application Protocol (CoAP)";
     }
}
